module ietf-mpls-tp-topology {
  //yang-version 1.1;

  namespace "urn:ietf:params:xml:ns:yang:ietf-mpls-tp-topology";
  prefix "mpls-tp-topo";

  import ietf-network {
    prefix "nw";
  }

  import ietf-network-topology {
    prefix "nt";
  }

  import ietf-te-topology {
    prefix "tet";
  }
  
  import ietf-mpls-tp-types {
    prefix "mpls-tp-types";
  }
  
  organization
    "Internet Engineering Task Force (IETF) TEAS WG";
  contact
    "
      WG List: <mailto:teas@ietf.org>

      ID-draft editor:
        Italo Busi (italo.busi@huawei.com);
        Haomian Zheng (zhenghaomian@huawei.com);
    ";
    
  description
    "This module defines technology-specific MPLS-TP topology
     data model.";

  revision 2019-03-11 {
    description
      "version -00 as an I-D";
    reference
      "draft-busizheng-teas-mpls-tp-yang";
  }
  
  augment "/nw:networks/nw:network/nw:network-types/"
        + "tet:te-topology" {
    container mpls-tp-topology {
      presence "indicates a topology type of MPLS-TP layer.";
      description "mpls-tp te topology type";
    }
    description "augment network types to include mpls-tp newtork";
  }
  
  augment "/nw:networks/nw:network/nt:link/tet:te/"
        + "tet:te-link-attributes/"
        + "tet:interface-switching-capability/tet:max-lsp-bandwidth/"
        + "tet:te-bandwidth/tet:technology" {
    when "../../../../../../../nw:network-types/tet:te-topology/"
       + "mpls-tp-topo:mpls-tp-topology" {
      description "MPLS-TP TE bandwidth.";
    }
    description "MPLS-TP bandwidth.";
    case mpls-tp {
      uses mpls-tp-types:mpls-tp-path-bandwidth;
    }
  }
  
  
  augment "/nw:networks/nw:network/nw:node/nt:termination-point/"
        + "tet:te/tet:interface-switching-capability/"
        + "tet:max-lsp-bandwidth/tet:te-bandwidth/tet:technology" {
    when "../../../../../../../nw:network-types/tet:te-topology/"
       + "mpls-tp-topo:mpls-tp-topology" {
      description "Augment MPLS-TP TE bandwidth";
    }
    description "MPLS-TP bandwidth.";
    case mpls-tp {
      uses mpls-tp-types:mpls-tp-path-bandwidth;
    }
  }  
  
  augment "/nw:networks/nw:network/nt:link/tet:te/"
        + "tet:te-link-attributes/tet:max-link-bandwidth/"
        + "tet:te-bandwidth/tet:technology" {
    when "../../../../../../nw:network-types/tet:te-topology/"
       + "mpls-tp-topo:mpls-tp-topology" {
      description "MPLS-TP TE bandwidth.";
    }
    description "MPLS-TP bandwidth.";
    case mpls-tp {
      uses mpls-tp-types:mpls-tp-bandwidth;
    }
  }
  
  augment "/nw:networks/nw:network/nt:link/tet:te/"
        + "tet:te-link-attributes/tet:max-resv-link-bandwidth/"
        + "tet:te-bandwidth/tet:technology" {
    when "../../../../../../nw:network-types/tet:te-topology/"
       + "mpls-tp-topo:mpls-tp-topology" {
      description "MPLS-TP TE bandwidth.";
    }
    description "MPLS-TP bandwidth.";
    case mpls-tp {
      uses mpls-tp-types:mpls-tp-bandwidth;
    }
  }  
  
  augment "/nw:networks/nw:network/nt:link/tet:te/"
        + "tet:te-link-attributes/tet:unreserved-bandwidth/"
        + "tet:te-bandwidth/tet:technology" {
    when "../../../../../../nw:network-types/tet:te-topology/"
       + "mpls-tp-topo:mpls-tp-topology" {
      description "MPLS-TP TE bandwidth.";
    }
    description "MPLS-TP bandwidth.";
    case mpls-tp {
      uses mpls-tp-types:mpls-tp-bandwidth;
    }
  }

  
}
