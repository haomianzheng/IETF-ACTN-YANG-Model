module ietf-mpls-tp-types {
  namespace "urn:ietf:params:xml:ns:yang:ietf-mpls-tp-types";
  prefix "mpls-tp-types";

  import ietf-routing-types {
    prefix "rt-types";
    
  }
  import ietf-eth-tran-types {
    prefix "etht-types";
    
  }
  organization
    "Internet Engineering Task Force (IETF) TEAS WG";
  contact
    "
      WG List: <mailto:teas@ietf.org>

      ID-draft editor:
        Italo Busi (italo.busi@huawei.com);
        Haomian Zheng (zhenghaomian@huawei.com);
    ";
  description
    "This module defines technology-specific MPLS-TP types
     data model.";
  revision 2019-03-11 {
    description
      "version -00 as an I-D";
    reference
      "draft-busizheng-teas-mpls-tp-yang";
  }
  
  grouping mpls-tp-path-bandwidth {
    description
      "Path bandwidth for MPLS-TP. ";
    leaf bandwidth-profile-name{
      type string;
      description "Name of Bandwidth Profile.";
    }
    leaf bandwidth-profile-type {
      type identityref {
        base etht-types:bandwidth-profile-type;
      }
      description "Type of Bandwidth Profile.";
    }
        
    leaf CIR {
      type uint64;
        description
          "Committed Information Rate in Kbps";
    }
        
    leaf EIR {
      type uint64;
      /*
        Need to indicate that EIR is not supported by RFC 2697

        must
            '../bw-profile-type = "etht-types:mef-10-bwp" or ' +
            '../bw-profile-type = "etht-types:rfc-2698-bwp" or ' +
            '../bw-profile-type = "etht-types:rfc-4115-bwp"'

        must
            '../bw-profile-type != "etht-types:rfc-2697-bwp"'
      */
      description
        "Excess Information Rate in Kbps
        In case of RFC 2698, PIR = CIR + EIR";
    }
    
    leaf CBS {
      type uint64;
      description
        "Committed Burst Size in in KBytes";
    }
    
    leaf EBS {
      type uint64;
      description
        "Excess Burst Size in KBytes.
          In case of RFC 2698, PBS = CBS + EBS";
    }
  }
  
  grouping mpls-tp-bandwidth {
    description
      "Bandwidth for MPLS-TP. ";
    leaf mpls-tp-bandwidth {
      type uint64{
        range "0..10000000000";
      }
      units "Kbps";
      description
        "Available bandwith value expressed in kilobits per second";
    }
  }
  
  grouping mpls-tp-path-label {
    description
      "Path Label for MPLS-TP. ";
    leaf mpls-label {
      type rt-types:mpls-label;
      description
        "MPLS-TP Label.";
    }
  }
}
