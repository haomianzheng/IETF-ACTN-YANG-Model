module ietf-otn-topology {
  yang-version 1.1;

  namespace "urn:ietf:params:xml:ns:yang:ietf-otn-topology";
  prefix "otntopo";

  import ietf-network {
    prefix "nw";
  }

  import ietf-network-topology {
    prefix "nt";
  }

  import ietf-te-topology {
    prefix "tet";
  }

  import ietf-otn-types {
    prefix "otn-types"; 
  }

  organization 
    "IETF CCAMP Working Group";
  contact
    "WG Web: <http://tools.ietf.org/wg/ccamp/>
     WG List: <mailto:ccamp@ietf.org>

     Editor: Haomian Zheng
             <mailto:zhenghaomian@huawei.com>

     Editor: Zheyu Fan
             <mailto:fanzheyu2@huawei.com>

     Editor: Anurag Sharma
             <mailto:ansha@google.com>

     Editor: Xufeng Liu
             <mailto:Xufeng_Liu@jabil.com>

     Editor: Sergio Belotti
             <mailto:sergio.belotti@nokia.com>

     Editor: Yunbin Xu
             <mailto:xuyunbin@ritt.cn>

     Editor: Lei Wang
             <mailto:wangleiyj@chinamobile.com>

     Editor: Oscar Gonzalez de Dios
             <mailto:oscar.gonzalezdedios@telefonica.com>";

  description
    "This module defines a protocol independent Layer 1/ODU topology
     data model.";

  revision 2017-10-30 {
    description
      "Revision 0.5";
    reference
      "draft-ietf-ccamp-otn-topo-yang-02.txt";
  }

 /*
  * Groupings
  */
  grouping otn-link-attributes {
    description "link attributes for OTN";

    list available-odu-info {
      key "priority";
      max-elements "8";
      description "List of ODU type and number on this link";
      leaf priority {
        type uint8 {
          range "0..7";
        }
        description "priority";
      }
      list odulist {
        key "odu-type";
        description 
          "the list of available ODUs per priority level";
        leaf odu-type {
          type identityref {
            base otn-types:tributary-protocol-type;
          }
          description "the type of ODU";
        }
        leaf number {
          type uint16;
          description "the number of odu type supported";
        }
        leaf tpn-range {
          type string {
            pattern "([1-9][0-9]{0,3}(-[1-9][0-9]{0,3})?"
                  + "(,[1-9][0-9]{0,3}(-[1-9][0-9]{0,3})?)*)";
          }
          description
            "A list of available tributary port number range
             between 1 and 9999.
             For example 1-20,25,50-1000";
          reference "RFC 7139: GMPLS Signaling Extensions for Control
                     of Evolving G.709 Optical Transport Networks";
        }
      }
      leaf ts-range {
        type string {
          pattern "([1-9][0-9]{0,3}(-[1-9][0-9]{0,3})?"
                + "(,[1-9][0-9]{0,3}(-[1-9][0-9]{0,3})?)*)";
        }
        description
          "A list of available tributary slot range
           between 1 and 9999.
           For example 1-20,25,50-1000";
        reference "RFC 7139: GMPLS Signaling Extensions for Control
                   of Evolving G.709 Optical Transport Networks";
      }
    }
    leaf tsg {
      type identityref {
        base otn-types:tributary-slot-granularity;
      }
      description "Tributary slot granularity.";
      reference
        "G.709/Y.1331, February 2016: Interfaces for the 
         Optical Transport Network (OTN)";
    }
    leaf distance {
      type uint32; 
      description "distance in the unit of kilometers";
    }
  }

  grouping otn-tp-attributes {
    description "tp attributes for OTN";
    list supported-payload-types {
      key "index";
      description
        "Supported payload types of a TP. The payload type is defined
         as the generalized PIDs in GMPLS.";
      leaf index {
        type uint16; 
        description "payload type index";
      }
      leaf payload-type {
        type string; 
        description "the payload type supported by this client tp";
        reference
          "http://www.iana.org/assignments/gmpls-sig-parameters
           /gmpls-sig-parameters.xhtml";
      }
    }
  }

 /*
  * Data nodes
  */
  augment "/nw:networks/nw:network/nw:network-types/"
        + "tet:te-topology" {
    container otn-topology {
      presence "indicates a topology type of Optical Transport 
                Network (OTN)-electrical layer.";
      description "otn topology type";
    }
    description "augment network types to include otn newtork";
  }

  augment "/nw:networks/nw:network/nt:link/tet:te/"
        + "tet:te-link-attributes" {
    when "../../../nw:network-types/tet:te-topology/"
       + "otntopo:otn-topology" {
      description "Augment only for otn network.";
    }
    description "Augment link configuration";
    uses otn-link-attributes;
  }

  augment "/nw:networks/nw:network/nw:node/nt:termination-point/"
        + "tet:te" {
    when "../../../nw:network-types/tet:te-topology/"
       + "otntopo:otn-topology" {
      description "Augment only for otn network";
    }
    description "OTN TP attributes config in ODU topology.";
    uses otn-tp-attributes;
  }
}
