module ietf-eth-te-tunnel {
    //TODO: FIXME
    yang-version 1.1;

    namespace "urn:ietf:params:xml:ns:yang:ietf-eth-tunnel";
    prefix "eth-tunnel";

    import ietf-te { prefix "te"; }
    import ietf-eth-tran-types { prefix "etht-types"; }

    organization
        "IETF CCAMP Working Group";

    contact
        "WG Web: <http://tools.ietf.org/wg/ccamp/>
        WG List: <mailto:ccamp@ietf.org>

        ID-draft editor:
         Aihua Guo (aihuaguo@huawei.com);
         Haomian Zheng (zhenghaomian@huawei.com)
        ";

    description
        "This module defines a model for ETH transport tunnel";

    revision "2017-09-04" {
        description
            "Revision 0.1";
        reference "TBD";
    }

    grouping eth-tunnel-endpoint {
        description "Parameters for ETH tunnel.";

        leaf vlanid {
          type etht-types:vlanid;
            description
               "VLAN tag id.";
        }

        leaf tag-type {
          type etht-types:eth-tag-type;
          description "VLAN tag type.";
        }
    }

    augment "/te:te/te:tunnels/te:tunnel/te:config" {
        description
                "Augment with additional parameters required for ETH
                service.";
                
        container src-eth-tunnel-endpoint {
            description
                "Source ETH tunnel endpoint.";
                
            uses eth-tunnel-endpoint;
        }
    
        container dst-eth-tunnel-endpoint {
            description
                "Destination ETH tunnel endpoint.";
                
            uses eth-tunnel-endpoint;
        }

        container bandwidth-profile {
            description
                "ETH tunnel bandwidth profile specification.";
                
            uses etht-types:etht-bandwidth-profiles;
        }
    }

    augment "/te:te/te:tunnels/te:tunnel/te:state" {
        description
                "Augment with additional parameters required for ETH
                service.";
                
        container src-eth-tunnel-endpoint {
            description
                "Source ETH tunnel endpoint.";
                
            uses eth-tunnel-endpoint;
        }
    
        container dst-eth-tunnel-endpoint {
            description
                "Destination ETH tunnel endpoint.";
                
            uses eth-tunnel-endpoint;
        }

        container bandwidth-profile {
            description
                "ETH tunnel bandwidth profile specification.";
                
            uses etht-types:etht-bandwidth-profiles;
        }
    }

}
