module ietf-eth-service-oam {
  yang-version 1.1;

  namespace "urn:ietf:params:xml:ns:yang:ietf-eth-service-oam";
  prefix "eth-oam";

  import ietf-eth-tran-service {
    prefix "ethtsvc";
  }
  
  import ietf-service-pm {
    prefix "svc-pm";
  }
  
  import ietf-trans-client-service {
    prefix "clntsvc";
  }
  
  import ietf-network {
    prefix nw;
  }

  organization
    "Internet Engineering Task Force (IETF) CCAMP WG";
  contact
    "
      WG List: <mailto:ccamp@ietf.org>
      ID-draft editor:
        Haomian Zheng (zhenghaomian@huawei.com);
        Italo Busi (italo.busi@huawei.com);
        Yanlei Zheng (zhengyanlei@chinaunicom.cn);
        Victor Lopez (victor.lopez@nokia.com);
        Oscar Gonzalez de Dios(oscar.gonzalezdedios@telefonica.com);
    ";

  description
    "This module defines the performance monitoring for Ethernet
     services OAM. The model fully conforms to the Network Management
     Datastore Architecture (NMDA).

     Copyright (c) 2021 IETF Trust and the persons
     identified as authors of the code.  All rights reserved.
     Redistribution and use in source and binary forms, with or
     without modification, is permitted pursuant to, and subject
     to the license terms contained in, the Simplified BSD License
     set forth in Section 4.c of the IETF Trust's Legal Provisions
     Relating to IETF Documents
     (https://trustee.ietf.org/license-info).
     This version of this YANG module is part of RFC XXXX; see
     the RFC itself for full legal notices.";

  revision 2021-07-10 {
    description
      "Initial version";
    reference
      "ADD REFERENCE HERE";
  }
  
  identity interval-type {
    description "Time interval";
  }
  
  identity interval-3p33ms {
    base interval-type;
    description "3.33 milliseconds";
  }
  
  identity interval-10ms {
    base interval-type;
    description "10 milliseconds";
  }
  
  identity interval-100ms {
    base interval-type;
    description "100 milliseconds";
  }
  
  identity interval-1s {
    base interval-type;
    description "1 second";
  }
  
  identity interval-10s {
    base interval-type;
    description "10 seconds";
  }
  
  identity interval-1m {
    base interval-type;
    description "1 minute";
  }
  
  identity interval-10m {
    base interval-type;
    description "10 minutes";
  }
  
  grouping eth-service-oam-config {
    container source {
      uses mep-config;
      description "OAM MEP configuration on source node.";
      }
    container destination {
      uses mep-config;
      description "OAM MEP configuration on destination node.";
      }
    uses interval-config;
    description "OAM configuration on Eth services.";
  }
  
  grouping interval-config {
    description "OAM Interval Configuration.";
    leaf cc-interval {
      type identityref {
        base interval-type;
      }
      description "Continuity check interval.";
    }

    leaf lm-interval {
      type identityref {
        base interval-type;
      }
      description "Loss measurement interval.";
    }

    leaf dm-interval {
      type identityref {
        base interval-type;
      }
      description "Delay measurement interval.";
    }
  }
  
  grouping mep-config {
    description "OAM MEP Configuration.";
    leaf md-name {
     type string;
     description
       "Name of Maintenance Domain.";
    } 
    leaf ma-name {
     type string;
     description
       "Name of Maintenance Domain.
        An maintenance association(MA) is a part of an MD. 
        An MD can be divided into one or more MAs. ";
    }

    leaf ma-level {
      type string;
      description
        "Maintenance Association Level.";
    }

    leaf meg-id {
      type string;
      description 
        "Comply with Y.1731 term, mapping with 802.lag MA name.";
    }
    leaf meg-level {
      type string;
      description "Mapping with 802.lag MA level.";
    }
    
    leaf mep-id {
      type uint8;
      description "0 if Abnormal";
    }

    leaf remote-mep-id {
      type uint8;
      description "The remote MEP ID must be specified.";
    }
  }


  augment "/svc-pm:performance-monitoring/svc-pm:service-pm" {
    description
      "Augment with additional parameters required for Ethernet OAM";
      
    container oam-config {
      description "OAM configuration container.";
      uses eth-service-oam-config;
    }
  }
  
  grouping errors {
    description "The grouping of error information.";
    leaf error-code {
      type uint32;
      description "The error code.";
    }
    
    leaf error-message {
      type string;
      description "The error message.";
    }
  }
  
  /*
    * Operations
    */
  rpc configure-oam {
    description "Deliver OAM configurations. ";
    
    input {
      list oam-config-list {
        key "service-name";
        description
          "The request list of service oam to be configured.";
        leaf service-name {
          type union {
            type leafref {
              path "/ethtsvc:etht-svc/ethtsvc:etht-svc-instances"
                 + "/ethtsvc:etht-svc-name";
            } 
            type leafref {
              path "/clntsvc:client-svc/clntsvc:client-svc-instances"
                 + "/clntsvc:client-svc-name";
            } 
          
          }
          mandatory true;
          description "The name of service.";
        }
        uses eth-service-oam-config;
      }
    }
    
    output {
      list oam-config-list {
        key "service-name";
        description "The OAM configuration list. ";        
        leaf service-name {
          type union {
            type leafref {
              path "/ethtsvc:etht-svc/ethtsvc:etht-svc-instances"
                 + "/ethtsvc:etht-svc-name";
            } 
            type leafref {
              path "/clntsvc:client-svc/clntsvc:client-svc-instances"
                       + "/clntsvc:client-svc-name";
            } 
          }
          mandatory true;
          description "The name of service.";
        }
      }  
        leaf result {
          type enumeration {
            enum success {
              description "success";
            }
            enum failure {
              description "failure";
            }
          }
          description "Result of OAM configuration.";
        }
        uses errors;
        
      }
    }
    
    rpc delete-oam-configurations {
      description "Delete OAM configurations. ";
        input {
          list service-list {
            key "service-name";            
            leaf service-name {
              type union {
                type leafref {
                  path "/ethtsvc:etht-svc/ethtsvc:etht-svc-instances"
                     + "/ethtsvc:etht-svc-name";
                } 
                type leafref {
                  path "/clntsvc:client-svc/clntsvc:client-svc-instances"
                     + "/clntsvc:client-svc-name";
                } 
              }
              mandatory true;
              description "The name of service.";
            }
            description "The list of service.";
          }
        }
    
        output {
          list oam-config-list {
            key "service-name";
            leaf service-name {
              type union {
                type leafref {
                  path "/ethtsvc:etht-svc/ethtsvc:etht-svc-instances"
                     + "/ethtsvc:etht-svc-name";
                } 
                type leafref {
                  path "/clntsvc:client-svc/clntsvc:client-svc-instances"
                     + "/clntsvc:client-svc-name";
                } 
              }
              mandatory true;
              description "The name of service.";
            }   
            
            leaf result {
              type enumeration {
                enum success {
                  description "success";
                }
                enum failure {
                  description "failure";
                }
              }
              description "The result of OAM deletion.";
            }
            
            uses errors;
            description "The list of service.";
          }
        }
    }
    
    rpc get-node-eth-oam-configurations {
      description "Get the Eth node OAM configuration info.";
      input {
        leaf-list te-node-list {
           type leafref {
             path "/nw:networks/nw:network/nw:node/nw:node-id";
           }
          description
            "Node identifier.  Must be same in the topology."; 
        }
      }
      
      output {
        list oam-list {
          leaf node-id {
            type leafref {
             path "/nw:networks/nw:network/nw:node/nw:node-id";
            }
            description "The node identifier.";
          }
          list mep-config-list {
            key "md-name ma-name meg-id mep-id";
            uses mep-config;
            description "The list of MEP configuration.";
          }
          description "The list of OAM.";
        }
      }
    }
}
