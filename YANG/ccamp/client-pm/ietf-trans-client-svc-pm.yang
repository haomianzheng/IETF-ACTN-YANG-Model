module ietf-trans-client-svc-pm {
  /* TODO: FIXME */
  yang-version 1.1;
  namespace "urn:ietf:params:xml:ns:yang:ietf-trans-client-svc-pm";
  prefix "clntsvc-pm";
  
  import ietf-trans-client-service {
    prefix "clntsvc";
  }
  
  import ietf-yang-types {
    prefix "yang";
  }

  import ietf-te-types {
    prefix "te-types";
  }
  
  organization
    "Internet Engineering Task Force (IETF) CCAMP WG";
  contact
    "
      WG List: <mailto:ccamp@ietf.org>

      ID-draft editor:
        Haomian Zheng (zhenghaomian@huawei.com);
        Italo Busi (italo.busi@huawei.com);
        Yanlei Zheng (zhengyanlei@chinaunicom.cn);
    ";

  description
    "This module defines the performance monitoring for transparent 
     client signals. The model fully conforms to the Network Management 
     Datastore Architecture (NMDA).
    
     Copyright (c) 2019 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).
     This version of this YANG module is part of RFC XXXX; see
     the RFC itself for full legal notices.";
     
  revision 2019-11-04 {
    description
      "Initial version";
    reference
      "ADD REFERENCE HERE";
  }
  
  container performance-monitoring {
    description 
      "This part is for performance monitoring. ";
    list service-pm {
      key "service-name";
      description
        "The list of service to be monitored.";
      leaf service-name {
        type leafref {
          path "/clntsvc:client-svc/clntsvc:client-svc-instances/clntsvc:client-svc-name";
        }
        description "The name of service.";
      }
    
      leaf pm-enable {
        type boolean;
        description
          "Indicate whether the performance monitoring 
          is enable or not.";
      }
    
      container latency-monitoring {
        description 
          "To monitor the latency of service.";
        leaf latency-measure-enable {
          type boolean;
          description
            "Indicate whether the latency measurement 
            is enable or not.";
        }
      
      }
      
      container service-pm-state {
        config false;
        description 
          "The state of service performance monitoring.";

        leaf start-time {
          type yang:date-and-time;
          description 
            "The time stamp when the service is started.";
        }
    
        leaf last-update-time {
          type yang:date-and-time;
          description 
            "The time stamp when the service is last updated.";
          
        }
    
        leaf latency {
          type uint32;
          units microsecond;
          description 
            "The latency of service.";
        }

        leaf error-message {
          type string;
          description 
            "The message of error.";
        }

        leaf service-oper-status {
          type identityref {
            base te-types:tunnel-state-type;
          
          }
          description 
            "The operational status of the services.";
        }
      }
    }
  }
}
