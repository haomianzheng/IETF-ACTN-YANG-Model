module ietf-eth-te-topology {
	/* TODO: FIXME */
	yang-version 1.1;

	namespace "urn:ietf:params:xml:ns:yang:ietf-eth-tran-topology";

	prefix "ethtetopo";

	import ietf-network {
		prefix "nd";
	}

	import ietf-network-topology {
		prefix "lnk";
	}

	import ietf-te-topology {
		prefix "tet";
	}

	import ietf-yang-types {
		prefix "yang";
	}

	import ietf-eth-tran-types {
		prefix "etht-types";
	}

	organization
		"Internet Engineering Task Force (IETF) CCAMP WG";
	contact
		"
			WG List: <mailto:ccamp@ietf.org>

			ID-draft editor:
				Italo Busi (italo.busi@huawei.com);
				Aihua Guo (aihuaguo@huawei.com);
				Haomian Zheng (zhenghaomian@huawei.com)
				Yunbin Xu (xuyunbin@ritt.cn)
				Yang Zhao (zhaoyangyjy@chinamobile.com)
		";

	description
		"This module defines a YANG data model for describing
                 layer-2 Ethernet transport topologies.";

	revision 2017-09-12 {
		description
			"Updated version:

				Moved eth-ltp-svc-attributes grouping to ietf-eth-tran-svc module.
			";
	}

	revision 2017-08-10 {
		description
			"Initial version";
	}

	/*
	Groupings
	*/

	grouping eth-tran-topology-type {
		description
			"Identifies the Ethernet Transport topology type";

		container eth-tran-topology {
			presence "indicates a topology type of Ethernet
				Transport Network.";
			description "Eth transport topology type";
		}
	}

	grouping eth-topology-attributes {
		description "Ethernet transport topology attributes";

		leaf name {
			type string;
			description "the topology name";
		}
	}

	grouping eth-node-attributes {
		description "Ethernet transport node attributes";

		leaf name {
			type string;
			description "a name for this node.";
		}
		leaf node-mac-address {
			type yang:mac-address;
			description "the MAC address of the node.";
		}
	}

	grouping eth-link-te-attributes {
		description "Ethernet TE link attributes";

		leaf max-bandwidth {
			type uint64{
				range "0..10000000000";
			}
			units "Kbps";
			description "Maximum bandwith value expressed in kilobits per second";
		}

		leaf available-bandwidth {
			type uint64{
				range "0..10000000000";
			}
			units "Kbps";
				description "Available bandwith value expressed in kilobits per second";
		}

		leaf available-vlan-range {
			type etht-types:vid-range-type;
			description
				"The range of the VLAN values that are available.";
		}
	}

	grouping eth-ltp-attributes {
		description "Ethernet transport link termination point attributes";

		leaf ltp-mac-address {
			type yang:mac-address;
			description "the MAC address of the LTP.";
		}
		leaf port-vlan-id {
			type etht-types:vlanid;
			description "the port VLAN ID of the LTP.";
		}
	}
	
	grouping eth-ltp-te-attributes {
		description "Ethernet transport link termination point TE attributes";

		/*
			Do we need the client-facing attribute?
			Cannot we use the svc container presence instead?
		*/
		leaf client-facing {
			type empty;
			description
				"if present, it means this tp is a client-facing ltp.";
		}
		leaf maximum-frame-size {
			type uint16 {
				range "64 .. 65535";
			}
			description
				"Maximum frame size";
		}
	}

	/*
	Data nodes
	*/

	augment "/nd:networks/nd:network/nd:network-types/tet:te-topology" {
		description "Augment network types to include ETH transport newtork";

		uses eth-tran-topology-type;
	}

	augment "/nd:networks/nd:network" {
		when "nd:network-types/tet:te-topology/eth-tran-topology" {
			description "Augment only for ETH transport network";
		}
		description "Augment ETH transport network topology attributes";

		uses eth-topology-attributes;
	}

	augment "/nd:networks/nd:network/nd:node" {
		when "../nd:network-types/tet:te-topology/eth-tran-topology" {
			description "Augment only for ETH transport network";
		}
		description "Augment ETH transport node attributes";

		uses eth-node-attributes;
	}
	
	augment "/nd:networks/nd:network/lnk:link/tet:te/tet:config" {
		when "../../../nd:network-types/tet:te-topology/eth-tran-topology" {
			description "Augment only for ETH transport network.";
		}
		description "Augment ETH transport link config attributes";

		uses eth-link-te-attributes;
	}

	augment "/nd:networks/nd:network/lnk:link/tet:te/tet:state" {
		when "../../../nd:network-types/tet:te-topology/eth-tran-topology" {
			description "Augment only for ETH transport network.";
		}
		description "Augment ETH transport link state attributes";

		uses eth-link-te-attributes;
	}

	augment "/nd:networks/nd:network/nd:node/lnk:termination-point" {
		when "../../nd:network-types/tet:te-topology/eth-tran-topology" {
			description "Augment only for ETH transport network";
		}
		description "Augment ETH LTP attributes";

		container config {
			description
				"ETH LTP configuration data.";
			uses eth-ltp-attributes;
			container access-link-bandwidth-profiles {
				uses etht-types:etht-bandwidth-profiles;
				description
					"Bandwidth profiles for access link.";
			}
		}
		container state {
			config false;
			description
				"ETH LTP operational state data.";
			uses eth-ltp-attributes;
			container access-link-bandwidth-profiles {
				uses etht-types:etht-bandwidth-profiles;
				description
					"Bandwidth profiles for access link.";
			}
		}
	}

	augment "/nd:networks/nd:network/nd:node/"
                +"lnk:termination-point/tet:te/tet:config" {
		when "../../nd:network-types/tet:te-topology/eth-tran-topology" {
			description "Augment only for ETH transport network";
		}
		description "Augment ETH transport LTP TE config attributes";

		uses eth-ltp-te-attributes;
	}

	augment "/nd:networks/nd:network/nd:node/"
                +"lnk:termination-point/tet:te/tet:state" {
		when "../../nd:network-types/tet:te-topology/eth-tran-topology" {
			description "Augment only for ETH transport network";
		}
		description "Augment ETH transport LTP TE state attributes";

		uses eth-ltp-te-attributes;
	}
}
